-- ============================================================================
-- Copyright (C) 2011 by  HUAWEI TECHNOLOGIES. All rights reserved.
-- Description:  This MIB module defines MIB objects which provides R2 attribute management.
-- Reference:  
-- Version: V1.02
-- ============================================================================

 HUAWEI-R2-MIB DEFINITIONS ::= BEGIN
      IMPORTS
        	MODULE-IDENTITY, OBJECT-TYPE, NOTIFICATION-TYPE, private
        		FROM SNMPv2-SMI
        	MODULE-COMPLIANCE, OBJECT-GROUP, NOTIFICATION-GROUP
        		FROM SNMPv2-CONF
        	TEXTUAL-CONVENTION
        		FROM SNMPv2-TC
        	IpAddress,TimeTicks,Counter32,Integer32
        		FROM SNMPv2-SMI
        	RowStatus,DisplayString
        		FROM SNMPv2-TC
        	huaweiUtility
        		FROM HUAWEI-MIB;
        
      hwR2Protocol MODULE-IDENTITY
                LAST-UPDATED "201111230000Z"
                ORGANIZATION "Huawei Technologies Co., Ltd."
                CONTACT-INFO                                        
                         "Huawei Industrial Base                
                          Bantian, Longgang                     
                          Shenzhen 518129                       
                          People's Republic of China            
                          Website: http://www.huawei.com        
                          Email: support@huawei.com             
                         "                                      
                DESCRIPTION 
                    "
                    This MIB module defines MIB objects which provides R2 attribute management.
                    "
      --  Revision history
            REVISION     "201120731000Z"
            DESCRIPTION  "V1.02, modify the description of hwRegisterOutgoingSignalType and hwRegisterIncomingSignalType"
            
            REVISION     "201111230000Z"
            DESCRIPTION  "V1.00, R2 attribute configure create a new mib document "
            
                        
                        ::= { huaweiUtility 108 }
                        
     hwR2Objects OBJECT IDENTIFIER ::= { hwR2Protocol 1 }
     
              
                        
               
hwR2ProfileTable OBJECT-TYPE
     SYNTAX      SEQUENCE OF HwR2ProfileEntry
     MAX-ACCESS  not-accessible
     STATUS      current
     DESCRIPTION
       "
       R2 signaling profile table,this table is used to add,modify,del,query R2 profile templet.
       The index of this table is hwR2ProfileIndex
       "
     ::= { hwR2Objects 1 }
 
   hwR2ProfileEntry OBJECT-TYPE
     SYNTAX      HwR2ProfileEntry
     MAX-ACCESS  not-accessible
     STATUS      current
     DESCRIPTION
       " 
       R2 signaling profile table,this table is used to add,modify,del,query R2 profile templet.
       The index of this entry is hwR2ProfileIndex
       "
     INDEX    {  
               hwR2ProfileIndex
              }
     ::= { hwR2ProfileTable 1 }
 
   HwR2ProfileEntry ::=
     SEQUENCE
     {
       hwR2ProfileIndex                       Integer32,
       hwSignalName                       OCTET STRING,
       hwSignalType                           Integer32,
       hwR2SignalProfileRowStatus             RowStatus
       }
 
   hwR2ProfileIndex OBJECT-TYPE
     SYNTAX      Integer32(0..15)
     MAX-ACCESS  not-accessible
     STATUS      current
     DESCRIPTION
         "
         R2 signaling profile index
         "
     ::= { hwR2ProfileEntry 1 }
 
   hwSignalName OBJECT-TYPE
     SYNTAX      OCTET STRING(SIZE (1..32))
     MAX-ACCESS  read-write
     STATUS      current
     DESCRIPTION
         "
         R2 signaling profile name
         "
     ::= { hwR2ProfileEntry 2 }
     
     hwSignalType OBJECT-TYPE
     SYNTAX      Integer32(0..15)
     MAX-ACCESS  read-write
     STATUS      current
     DESCRIPTION
         "
         R2 signaling type
         "
     ::= { hwR2ProfileEntry 3 }
 
   hwR2SignalProfileRowStatus OBJECT-TYPE
     SYNTAX      RowStatus
     MAX-ACCESS  read-write
     STATUS      current
     DESCRIPTION
         "
         Row status of R2 signaling profile 
         "
     ::= { hwR2ProfileEntry 4 }
     
   
   hwRegisterSignalAttributeTable OBJECT-TYPE
     SYNTAX      SEQUENCE OF HwRegisterSignalAttributeEntry
     MAX-ACCESS  not-accessible
     STATUS      current
     DESCRIPTION
       "
       R2 register signaling attribute table,this table is used to set and query r2 profile register attribute
       The index of this table is hwRegisterSignalIndex
       "
     ::= { hwR2Objects 2 }
 
   hwRegisterSignalAttributeEntry OBJECT-TYPE
     SYNTAX      HwRegisterSignalAttributeEntry
     MAX-ACCESS  not-accessible
     STATUS      current
     DESCRIPTION
       "
       R2 register signaling attribute table,this table is used to set and query r2 profile register attribute 
       The index of this entry is  hwRegisterSignalIndex
       "
     INDEX    {  
               hwRegisterSignalIndex
              }
     ::= { hwRegisterSignalAttributeTable 1 }
 
   HwRegisterSignalAttributeEntry ::=
     SEQUENCE
     {
       hwRegisterSignalIndex        Integer32,
       hwRegisterOutgoingSignalType         INTEGER,
       hwSignalSendVoltage            Integer32,
       hwBackPulseTime              Integer32,
       hwDTMFSendTime               Integer32,
       hwDTMFSendInterval           Integer32,
       hwNoCallerPermit             INTEGER, 
       hwNumberMaxInterval          Integer32,
       hwSignalKeepMaxTime          Integer32,
       hwReceiveNumberMaxInterval   Integer32,
       hwSignalStopPermitTime       Integer32,
       hwWaitCallerCategoryTime         Integer32,
       hwWaitBsignalTime            Integer32,
       hwNumberSendMode             INTEGER, 
       hwCallingNumberMaxLength         Integer32,
       hwCompellingSequenceKeepaliveTime  Integer32,
       hwSendPulseSignal            INTEGER,
       hwRegisterIncomingSignalType INTEGER  
     }
 
   hwRegisterSignalIndex OBJECT-TYPE
     SYNTAX      Integer32(0..15)
     MAX-ACCESS  not-accessible
     STATUS      current
     DESCRIPTION
         "
         R2 signaling profile index
         "
     ::= { hwRegisterSignalAttributeEntry 1 }
     
   hwRegisterOutgoingSignalType OBJECT-TYPE
     SYNTAX      INTEGER{mfc(1),pulse(2),dtmf(3),mfp(4),dpmfp(5)}
     MAX-ACCESS  read-write
     STATUS      current
     DESCRIPTION
         "
          Signaling type of outgoing office register
          Options:
              1. mfc(1)-the register outgoing signal type is mfc
              2. pulse(2) -the register outgoing signal type is pulse
              3. dtmf(3) -the register outgoing signal type is dtmf
              4. mfp(4) -the register outgoing signal type is mfp
              5. dpmfp(5) -the register outgoing signal type is dpmfp
         "
         DEFVAL      { mfc }
     ::= { hwRegisterSignalAttributeEntry 2 } 
 
   hwSignalSendVoltage OBJECT-TYPE
     SYNTAX      Integer32(1..23)
     MAX-ACCESS  read-write
     STATUS      current
     DESCRIPTION
         "
         Register signal transmit level(dbm)
         1:-25dBm
         2:-24dBm
         3:-23dBm
         4:-22dBm
         5:-21dBm
         6:-20dBm
         7:-19dBm
         8:-18dBm
         9:-17dBm
         10:-16dBm
         11:-15dBm
         12:-14dBm
         13:-13dBm
         14:-12dBm
         15:-11dBm
         16:-10dBm
         17:-9dBm
         18:-8dBm
         19:-7dBm
         20:-6dBm
         21:-5dBm
         22:-4dBm
         23:-3dBm}
         "
         DEFVAL      { 14 }
     ::= { hwRegisterSignalAttributeEntry 3 }
 
   hwBackPulseTime OBJECT-TYPE
     SYNTAX      Integer32(100..200)
     MAX-ACCESS  read-write
     STATUS      current
     DESCRIPTION
         "
         Backword pulse duration(Multiple of 10; unit: ms)
         "
         DEFVAL      { 150 }
     ::= { hwRegisterSignalAttributeEntry 4 }
 
   hwDTMFSendTime OBJECT-TYPE
     SYNTAX      Integer32(50..200)
     MAX-ACCESS  read-write
     STATUS      current
     DESCRIPTION
         "
         DTMF signal transmit duration (ms)
         
         "
         DEFVAL      { 68 }
     ::= { hwRegisterSignalAttributeEntry 5 }
 
   hwDTMFSendInterval OBJECT-TYPE
     SYNTAX      Integer32(50..500)
     MAX-ACCESS  read-write
     STATUS      current
     DESCRIPTION
         "
         DTMF signal transmit interval (ms)
         "
         DEFVAL      { 68 }
     ::= { hwRegisterSignalAttributeEntry 6 }
 
   hwNoCallerPermit OBJECT-TYPE
     SYNTAX      INTEGER{yes(1),no(2)}
     MAX-ACCESS  read-write
     STATUS      obsolete
     DESCRIPTION
         "
         Can the call be established without a calling party
         Options:
         1. yes(1)- permit send caller number
         2. no(2) - not permit send caller number
         "
     ::= { hwRegisterSignalAttributeEntry 7 }
 
   hwNumberMaxInterval OBJECT-TYPE
     SYNTAX      Integer32(1..60)
     MAX-ACCESS  read-write
     STATUS      current
     DESCRIPTION
         "
         Max. dialing interval (s)
         "
         DEFVAL      { 50 }
     ::= { hwRegisterSignalAttributeEntry 8 }
 
   hwSignalKeepMaxTime OBJECT-TYPE
     SYNTAX      Integer32(1..30)        
     MAX-ACCESS  read-write
     STATUS      obsolete
     DESCRIPTION
         "
         Max. signal duration (s)
         "
     ::= { hwRegisterSignalAttributeEntry 9 }
 
   hwReceiveNumberMaxInterval OBJECT-TYPE
     SYNTAX      Integer32(1..60)
     MAX-ACCESS  read-write
     STATUS      obsolete
     DESCRIPTION
         "
         Max. interval of receiving calling(callee) signals (s)
         "
     ::= { hwRegisterSignalAttributeEntry 10 }
 
   hwSignalStopPermitTime OBJECT-TYPE
     SYNTAX      Integer32(1..30)
     MAX-ACCESS  read-write
     STATUS      obsolete
     DESCRIPTION
         "
         Max. duration of signal interruption 
         "
     ::= { hwRegisterSignalAttributeEntry 11 }
     
 hwWaitCallerCategoryTime   OBJECT-TYPE  
      SYNTAX      Integer32(1..60)   
      MAX-ACCESS  read-write        
      STATUS      current          
      DESCRIPTION                  
          "  
          Wait time for receiving calling party type (s)                        
          "     
          DEFVAL      { 50 }                   
      ::= { hwRegisterSignalAttributeEntry 12 }
      
hwWaitBsignalTime   OBJECT-TYPE   
     SYNTAX      Integer32(1..60)           
     MAX-ACCESS  read-write               
     STATUS      current                  
     DESCRIPTION                           
         "                                 
         Wait time for receiving group B signal (s)             
         "   
         DEFVAL      { 50 }                               
     ::= { hwRegisterSignalAttributeEntry 13 }  
     
hwNumberSendMode   OBJECT-TYPE        
     SYNTAX      INTEGER{immediate(1),delay(2)}                
     MAX-ACCESS  read-write                     
     STATUS      current                       
     DESCRIPTION                               
         "   
         Signal transmit mode     
         Options:
         1. immediate(1)- number send immediately
         2. delay(2) - number send delay                                              
         "      
         DEFVAL      { delay }                                       
     ::= { hwRegisterSignalAttributeEntry 14 } 
     
 hwCallingNumberMaxLength   OBJECT-TYPE        
     SYNTAX      Integer32(0..32)                
     MAX-ACCESS  read-write                     
     STATUS      current                       
     DESCRIPTION                               
         "                                     
         Max. length of calling number              
         "      
         DEFVAL      { 12 }                                  
     ::= { hwRegisterSignalAttributeEntry 15 }    
       
  hwCompellingSequenceKeepaliveTime   OBJECT-TYPE        
     SYNTAX      Integer32(0..60000)                
     MAX-ACCESS  read-write                    
     STATUS      current                       
     DESCRIPTION                               
         "               
         Compelling sequence keepalive time for register signaling (ms)                      
                        
         "         
         DEFVAL      { 40000 }                                      
     ::= { hwRegisterSignalAttributeEntry 16 }   
     
 hwSendPulseSignal   OBJECT-TYPE        
     SYNTAX      INTEGER{yes(1),no(2)}                
     MAX-ACCESS  read-write                     
     STATUS      current                       
     DESCRIPTION                               
         "                                     
         Whether to send sending-finished signals 
         Options:
         1. yes(1)- send pulse signal 
         2. no(2) - do not send pulse signal                  
         "   
         DEFVAL      { no }                                           
     ::= { hwRegisterSignalAttributeEntry 17 }    
 
 hwRegisterIncomingSignalType OBJECT-TYPE
     SYNTAX      INTEGER{mfc(1),pulse(2),dtmf(3),mfp(4),dpmfp(5)}
     MAX-ACCESS  read-write
     STATUS      current
     DESCRIPTION
         "
         Signaling type of incoming office register
         Options:
          1. mfc(1)-the register incoming signal type is mfc
          2. pulse(2) -the register incoming signal type is pulse
          3. dtmf(3) -the register incoming signal type is dtmf
          4. mfp(4) -the register incoming signal type is mfp
          5. dpmfp(5) -the register incoming signal type is dpmfp 
         "
         DEFVAL      { mfc }
     ::= { hwRegisterSignalAttributeEntry 18 }     
     
     
     
     
 hwLineSignalAttributeTable OBJECT-TYPE
     SYNTAX      SEQUENCE OF HwLineSignalAttributeEntry
     MAX-ACCESS  not-accessible
     STATUS      current
     DESCRIPTION
       "
       R2 line signaling attribute table,this table is used to set and query r2 profile line signal attribute.
       The index of this table is hwLineSignalIndex
       "
     ::= { hwR2Objects 3 }
 
   hwLineSignalAttributeEntry OBJECT-TYPE
     SYNTAX      HwLineSignalAttributeEntry
     MAX-ACCESS  not-accessible
     STATUS      current
     DESCRIPTION
       "
       R2 line signaling attribute table,this table is used to set and query r2 profile line signal attribute.
       The index of this entry is hwLineSignalIndex
       "
     INDEX    {  
               hwLineSignalIndex
              }
     ::= { hwLineSignalAttributeTable 1 }
 
   HwLineSignalAttributeEntry ::=
     SEQUENCE
     {
       hwLineSignalIndex                 Integer32,
       hwLineSignalType                  INTEGER,
       hwWaitSeizeAckTime            Integer32,
       hwWaitAnswerTime             Integer32,
       hwWaitClearForwardTime            Integer32,
       hwWaitProtectTime                 Integer32
    }
 
   hwLineSignalIndex OBJECT-TYPE
     SYNTAX      Integer32(0..15)
     MAX-ACCESS  not-accessible
     STATUS      current
     DESCRIPTION
         "
          R2 profile index
         "
     ::= { hwLineSignalAttributeEntry 1 }
     
   hwLineSignalType OBJECT-TYPE
     SYNTAX     INTEGER{l1b(1),l2b(2),l3b(3),pulse(4)}
     MAX-ACCESS  read-write
     STATUS      obsolete
     DESCRIPTION
         "
         Line signaling type
         Options: 
          1. l1b(1)-line signal type is l1b
          2. l2b(2) -line signal type is l2b
          3. l3b(3) -line signal type is l3b
          4. pulse(4) -line signal type is pulse
         
         "
     ::= { hwLineSignalAttributeEntry 2 }    
     
 
   hwWaitSeizeAckTime OBJECT-TYPE
     SYNTAX      Integer32(0..7000)
     MAX-ACCESS  read-write
     STATUS      current
     DESCRIPTION
         "
         Wait time for receiving occupation verification signal (ms)
         "
         DEFVAL      { 5000 }
     ::= { hwLineSignalAttributeEntry 3 }
 
   hwWaitAnswerTime OBJECT-TYPE
     SYNTAX      Integer32(0..511)
     MAX-ACCESS  read-write
     STATUS      current
     DESCRIPTION
         "
         Wait time for receiving answer signal (s)
         "
         DEFVAL      { 300 }
     ::= { hwLineSignalAttributeEntry 4 }
 
   hwWaitClearForwardTime OBJECT-TYPE
     SYNTAX      Integer32(0..2000)
     MAX-ACCESS  read-write
     STATUS      current
     DESCRIPTION
         "
         Wait time for receiving forward release signal (ms)
         "
         DEFVAL      { 200 }
     ::= { hwLineSignalAttributeEntry 5 }
 
   hwWaitProtectTime OBJECT-TYPE
     SYNTAX      Integer32(0..2000)
     MAX-ACCESS  read-write
     STATUS      current
     DESCRIPTION
         "
         Wait time for receiving release protection signal (ms)
         "
         DEFVAL      { 200 }
     ::= { hwLineSignalAttributeEntry 6 }
 
         
                 
hwAddressSendListTable OBJECT-TYPE
     SYNTAX      SEQUENCE OF HwAddressSendListEntry
     MAX-ACCESS  not-accessible
     STATUS      current
     DESCRIPTION
       "
       Attribute table for sent R2 address,this table is used to set and query register address send attribute. 
       The index of this table is  hwAddresssendInformationIndex
       "
     ::= { hwR2Objects 4 }
 
   hwAddressSendListEntry OBJECT-TYPE
     SYNTAX      HwAddressSendListEntry
     MAX-ACCESS  not-accessible
     STATUS      current
     DESCRIPTION
       "
       Attribute table for sent R2 address,this table is used to set and query register address send attribute. 
       The index of this entry is hwAddresssendInformationIndex
       
       "
     INDEX    {  
               hwAddresssendInformationIndex
              }
     ::= { hwAddressSendListTable 1 }
 
   HwAddressSendListEntry ::=
     SEQUENCE
     {
       hwAddresssendInformationIndex          Integer32,
       hwAddressSendInformationDI          INTEGER,
       hwAddressSendInformationSI          INTEGER,
       hwAddressSendInformationSC          INTEGER,
       hwAddressSendInformationES          INTEGER,
       hwAddressSendInformationCC          INTEGER,
       hwAddressSendInformationDISC        INTEGER,
       hwAddressSendInformationNAC         INTEGER,
       hwAddressSendInformationSP          INTEGER

    }     
     
  hwAddresssendInformationIndex OBJECT-TYPE
     SYNTAX      Integer32(0..15)
     MAX-ACCESS  not-accessible
     STATUS      current
     DESCRIPTION
         "
          R2 profile index
         "
     ::= { hwAddressSendListEntry 1 }   
 
 hwAddressSendInformationDI OBJECT-TYPE
     SYNTAX      INTEGER{yes(1)}
     MAX-ACCESS  read-only
     STATUS      obsolete
     DESCRIPTION
         "
          Whether to send called numbers
          Options: 
          1. yes(1)-register signal address send callee number
         
         "
     ::= { hwAddressSendListEntry 2 } 
     
 hwAddressSendInformationSI OBJECT-TYPE
     SYNTAX      INTEGER{yes(1),no(2)}
     MAX-ACCESS  read-write
     STATUS      current
     DESCRIPTION
         "
          Whether to send calling numbers
          Options: 
          1. yes(1)-register signal address send caller number
          2. no(2)-register signal address does not send caller number
         "
         DEFVAL      { yes }
     ::= { hwAddressSendListEntry 3 }
     
hwAddressSendInformationSC OBJECT-TYPE
     SYNTAX      INTEGER{yes(1)}
     MAX-ACCESS  read-only
     STATUS      obsolete
     DESCRIPTION
         "
           Whether to send calling party types
           Options: 
           1. yes(1)-register signal address send caller type
         "
     ::= { hwAddressSendListEntry 4 }     

hwAddressSendInformationES OBJECT-TYPE
     SYNTAX      INTEGER{yes(1),no(2)}
     MAX-ACCESS  read-write
     STATUS      current
     DESCRIPTION
         "
          Whether to send echo cancelation info
          Options: 
          1. yes(1)-register signal address send echo suppression
          2. no(2)-register signal address does not send echo suppression
         "
         DEFVAL      { no }
     ::= { hwAddressSendListEntry 5 } 
     
hwAddressSendInformationCC OBJECT-TYPE
     SYNTAX      INTEGER{yes(1),no(2)}
     MAX-ACCESS  read-write
     STATUS      current
     DESCRIPTION
         "
          Whether to send country code
          Options: 
          1. yes(1)-register signal address send country code
          2. no(2)-register signal address does not send country code
         "
         DEFVAL      { no }
     ::= { hwAddressSendListEntry 6 } 
     
hwAddressSendInformationDISC OBJECT-TYPE
     SYNTAX      INTEGER{yes(1),no(2)}
     MAX-ACCESS  read-write
     STATUS      current
     DESCRIPTION
         "
          Whether to send separating signaling
          Options: 
          1. yes(1)-register signal address send discrimination flag
          2. no(2)-register signal address does not send discrimination flag
         "
         DEFVAL      { no }
     ::= { hwAddressSendListEntry 7 } 
     
hwAddressSendInformationNAC OBJECT-TYPE
     SYNTAX      INTEGER{yes(1),no(2)}
     MAX-ACCESS  read-write
     STATUS      current
     DESCRIPTION
         "
          Whether to send circuit basic info
          Options: 
          1. yes(1)-register signal address send circuit character
          2. no(2)-register signal address does not send circuit character
         "
         DEFVAL      { no }
     ::= { hwAddressSendListEntry 8 } 
     
hwAddressSendInformationSP OBJECT-TYPE
     SYNTAX      INTEGER{yes(1),no(2)}
     MAX-ACCESS  read-only
     STATUS      obsolete
     DESCRIPTION
         "
          Whether to send the calling priority
          Options: 
          1. yes(1)-register signal address send caller priority
          2. no(2)-register signal address does not send caller priority
         "
     ::= { hwAddressSendListEntry 9 } 
     
     
hwAddressReceiveListTable OBJECT-TYPE
     SYNTAX      SEQUENCE OF HwAddressReceiveListEntry
     MAX-ACCESS  not-accessible
     STATUS      current
     DESCRIPTION
       "
       Attribute table for received R2 address,this table is used to set and query register signal address receive attribute
       The index of this table is hwAddressReceiveInformationIndex
       "
     ::= { hwR2Objects 5 }
 
   hwAddressReceiveListEntry OBJECT-TYPE
     SYNTAX      HwAddressReceiveListEntry
     MAX-ACCESS  not-accessible
     STATUS      current
     DESCRIPTION
       "
       Attribute table for received R2 address,this table is used to set and query register signal address receive attribute
       The index of this entry is hwAddressReceiveInformationIndex
       "
     INDEX    {  
               hwAddressReceiveInformationIndex
              }
     ::= { hwAddressReceiveListTable 1 }
 
   HwAddressReceiveListEntry ::=
     SEQUENCE
     {
       hwAddressReceiveInformationIndex         Integer32, 
       hwAddressReceiveInformationDI         INTEGER,
       hwAddressReceiveInformationSI         INTEGER,
       hwAddressReceiveInformationSC         INTEGER,
       hwAddressReceiveInformationES         INTEGER,
       hwAddressReceiveInformationCC         INTEGER,
       hwAddressReceiveInformationDISC       INTEGER,
       hwAddressReceiveInformationNAC        INTEGER,
       hwAddressReceiveInformationSP         INTEGER,
       hwRequestCallerLineNoPosition        Integer32,
       hwRequestCallerLineTypePosition      Integer32


    }     
     
  hwAddressReceiveInformationIndex OBJECT-TYPE
     SYNTAX      Integer32(0..15)
     MAX-ACCESS  not-accessible
     STATUS      current
     DESCRIPTION
         "
          R2 profile index
         "
     ::= { hwAddressReceiveListEntry 1 }   
 
 hwAddressReceiveInformationDI OBJECT-TYPE
     SYNTAX      INTEGER{yes(1)}
     MAX-ACCESS  read-only
     STATUS      obsolete
     DESCRIPTION
         "
          Whether to receive called numbers
           Options: 
          1. yes(1)-register signal address receive callee number
         "
     ::= { hwAddressReceiveListEntry 2 } 
     
 hwAddressReceiveInformationSI OBJECT-TYPE
     SYNTAX      INTEGER{yes(1),no(2)}
     MAX-ACCESS  read-write
     STATUS      current
     DESCRIPTION
         "
          Whether to receive calling numbers
          Options: 
          1. yes(1)-register signal address receive calling number
          2. no(2)-register signal address does not receive calling number
         "
         DEFVAL      { yes }
     ::= { hwAddressReceiveListEntry 3 }
     
hwAddressReceiveInformationSC OBJECT-TYPE
     SYNTAX      INTEGER{yes(1),no(2)}
     MAX-ACCESS  read-write
     STATUS      current
     DESCRIPTION
         "
          Whether to receive calling party types
           Options: 
          1. yes(1)-register signal address receive calling user type
          2. no(2)-register signal address does not receive calling user type
         "
         DEFVAL      { yes }
     ::= { hwAddressReceiveListEntry 4 }     

hwAddressReceiveInformationES OBJECT-TYPE
     SYNTAX      INTEGER{yes(1),no(2)}
     MAX-ACCESS  read-write
     STATUS      current
     DESCRIPTION
         "
          Whether to receive echo cancelation info
          Options: 
          1. yes(1)-register signal address receive echo suppression
          2. no(2)-register signal address does not receive echo suppression
         "
         DEFVAL      { no }
     ::= { hwAddressReceiveListEntry 5 } 
     
hwAddressReceiveInformationCC OBJECT-TYPE
     SYNTAX      INTEGER{yes(1),no(2)}
     MAX-ACCESS  read-write
     STATUS      current
     DESCRIPTION
         "
          Whether to receive country code
          Options: 
          1. yes(1)-register signal address receive country code
          2. no(2)-register signal address does not receive country code
         "
         DEFVAL      { no }
     ::= { hwAddressReceiveListEntry 6 } 
     
hwAddressReceiveInformationDISC OBJECT-TYPE
     SYNTAX      INTEGER{yes(1),no(2)}
     MAX-ACCESS  read-write
     STATUS      current
     DESCRIPTION
         "
          Whether to receive separating signaling
          Options: 
          1. yes(1)-register signal address receive distinctive indication
          2. no(2)-register signal address does not receive distinctive indication
         "
         DEFVAL      { no }
     ::= { hwAddressReceiveListEntry 7 } 
     
hwAddressReceiveInformationNAC OBJECT-TYPE
     SYNTAX      INTEGER{yes(1),no(2)}
     MAX-ACCESS  read-write
     STATUS      current
     DESCRIPTION
         "
          Whether to receive circuit basic info
          Options: 
          1. yes(1)-register signal address receive circuit character
          2. no(2)-register signal address does not receive circuit character
         "
         DEFVAL      { no }
     ::= { hwAddressReceiveListEntry 8 } 
     
hwAddressReceiveInformationSP OBJECT-TYPE
     SYNTAX      INTEGER{yes(1),no(2)}
     MAX-ACCESS  read-only
     STATUS      obsolete
     DESCRIPTION
         "
          Whether to receive calling priority
          Options: 
          1. yes(1)-register signal address receive caller priority
          2. no(2)-register signal address does not receive caller priority
         "
     ::= { hwAddressReceiveListEntry 9 } 
     
hwRequestCallerLineNoPosition OBJECT-TYPE
     SYNTAX      Integer32(1..12)
     MAX-ACCESS  read-write
     STATUS      current
     DESCRIPTION
         "
          Called number digits before requesting calling number (The calling number must be requested after the calling party type.)
         "
         DEFVAL      { 1 }
     ::= { hwAddressReceiveListEntry 10 }
     
hwRequestCallerLineTypePosition OBJECT-TYPE
     SYNTAX      Integer32(1..12)
     MAX-ACCESS  read-write
     STATUS      current
     DESCRIPTION
         "
        Called number digits before requesting calling party type (The calling party type must be requested before the calling number.)
         "
         DEFVAL      { 1 }
     ::= { hwAddressReceiveListEntry 11 }    


hwR2SignalTypeVersionTable  OBJECT IDENTIFIER ::={ hwR2Objects 6 }

hwSignalTypeVersion OBJECT-TYPE
    SYNTAX      OCTET STRING(SIZE (1..10))
    MAX-ACCESS  read-only
    STATUS      current
    DESCRIPTION
      " 
      Version of R2 signaling type file 
      "
    ::= { hwR2SignalTypeVersionTable 1 }
    
hwR2SignalTypeTable OBJECT-TYPE
     SYNTAX      SEQUENCE OF HwR2SignalTypeEntry
     MAX-ACCESS  not-accessible
     STATUS      current
     DESCRIPTION
       "
       R2 signaling type table,this table is used to query R2 signal type information
       The index of this table is hwSignalTypeIndex
       "
     ::= { hwR2Objects 7 }
 
   hwR2SignalTypeEntry OBJECT-TYPE
     SYNTAX      HwR2SignalTypeEntry
     MAX-ACCESS  not-accessible
     STATUS      current
     DESCRIPTION
       "
       R2 signaling type table,this table is used to query R2 signal type information
       The index of this entry is hwSignalTypeIndex
       "
     INDEX    {  
               hwSignalTypeIndex
              }
     ::= { hwR2SignalTypeTable 1 }
 
   HwR2SignalTypeEntry ::=
     SEQUENCE
     {
       hwSignalTypeIndex                  Integer32,
       hwSignalTypeName                       OCTET STRING
      
       }
 
   hwSignalTypeIndex OBJECT-TYPE
     SYNTAX      Integer32(0..15)
     MAX-ACCESS  not-accessible
     STATUS      current
     DESCRIPTION
         "
         R2 signaling type index
         "
     ::= { hwR2SignalTypeEntry 1 }
 
   hwSignalTypeName OBJECT-TYPE
     SYNTAX      OCTET STRING(SIZE (0..32))
     MAX-ACCESS  read-write
     STATUS      current
     DESCRIPTION
         "
         R2 signaling type name
         The names of the preconfigured multiple countries adaption profiles with IDs ranging from 0 to 9 cannot be modified
         "
     ::= { hwR2SignalTypeEntry 2 }
  
      
END
